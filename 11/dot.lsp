(command "donut" 0.1 0.1 '(49 51)"")
(command "donut" 0.1 0.1 '(34 44)"")
(command "donut" 0.1 0.1 '(44 71)"")
(command "donut" 0.1 0.1 '(82 8)"")
(command "donut" 0.1 0.1 '(64 5)"")
(command "donut" 0.1 0.1 '(0 32)"")
(command "donut" 0.1 0.1 '(23 13)"")
(command "donut" 0.1 0.1 '(47 35)"")
(command "donut" 0.1 0.1 '(54 72)"")
(command "line" '(93 395.9806310857132)'(49 51))
